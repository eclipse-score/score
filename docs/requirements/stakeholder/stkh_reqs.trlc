/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/
package StkhReqs

import ScoreReq
import ScoreType

ScoreReq.StkhReq interprocess_communication {
    title = "Interprocess Communication"
    description = "The platform shall support inter-process communication."
    rationale = "Application software typically consists of multiple processes which need to interact."
    status = ScoreType.Status.valid
    reqtype = ScoreType.Reqtype.functional
    safety = ScoreType.Asil.B
    version = 1
}
