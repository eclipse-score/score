/********************************************************************************
 * Copyright (c) 2025 Contributors to the Eclipse Foundation
 *
 * See the NOTICE file(s) distributed with this work for additional
 * information regarding copyright ownership.
 *
 * This program and the accompanying materials are made available under the
 * terms of the Apache License Version 2.0 which is available at
 * https://www.apache.org/licenses/LICENSE-2.0
 *
 * SPDX-License-Identifier: Apache-2.0
 ********************************************************************************/

package AUTOSAR_r24_11_Req

import ScoreReq
import ScoreType

section "SOMEIP" {

    Autosar_r24_11_StdReq PRS_SOMEIP_00137 {
        id = "PRS_SOMEIP_00137"
        safety = ScoreType.Asil.QM
    }

    Autosar_r24_11_StdReq PRS_SOMEIP_00139 {
        id = "PRS_SOMEIP_00139"
        safety = ScoreType.Asil.QM
    }

    Autosar_r24_11_StdReq PRS_SOMEIP_00512 {
        id = "PRS_SOMEIP_00512"
        safety = ScoreType.Asil.QM
    }
}
